"""FreeCAD Macro to create Dim Sum Organizer insert.

This macro reloads all Python files and creates the FreeCAD document.
"""

import FreeCAD
import importlib
import sys
import os

# Get the macro directory
macro_dir = os.path.dirname(__file__)

# Add to path if not already there
if macro_dir not in sys.path:
    sys.path.insert(0, macro_dir)

# Reload modules
try:
    if "config" in sys.modules:
        importlib.reload(sys.modules["config"])
    if "create_insert" in sys.modules:
        importlib.reload(sys.modules["create_insert"])
except KeyError:
    pass

# Import modules
import config
import create_insert

# Close existing document if it exists
if FreeCAD.ActiveDocument:
    FreeCAD.closeDocument(FreeCAD.ActiveDocument.Name)

# Create new document
doc = FreeCAD.newDocument("DimSumOrganizer")

create_insert.create_insert(doc)

# Recompute
doc.recompute()

# Set to isometric view and fit all
if FreeCAD.GuiUp:
    import FreeCADGui
    
    # Get the active view
    view = FreeCADGui.activeDocument().activeView()
    
    # Set to isometric view
    view.viewIsometric()
    
    # Fit all objects to view
    view.fitAll()

FreeCAD.Console.PrintMessage("Dim Sum Organizer insert created successfully!\n")
