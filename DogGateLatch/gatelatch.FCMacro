# -*- coding: utf-8 -*-

import FreeCADGui as Gui
import FreeCAD as App
import os
import sys
from importlib import reload


# Change to the directory containing this macro
macro_dir = os.path.dirname(os.path.realpath(__file__))
os.chdir(macro_dir)

if '' not in sys.path:
    sys.path.insert(0, '')

try:
    App.closeDocument('GateLatch')
except NameError:
    pass
    
if 'GateLatch' not in sys.modules:
    import latch
reload(latch)
latch.main()

#Gui.activeDocument().activeView().viewTop()
Gui.activeDocument().activeView().viewIsometric()
Gui.SendMsgToActiveView("ViewFit") 
Gui.Selection.clearSelection()
Gui.Selection.addSelection('GateLatch','Base')
Gui.runCommand('Std_ToggleTransparency',0)
