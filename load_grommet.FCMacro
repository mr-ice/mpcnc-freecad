# -*- coding: utf-8 -*-

# Macro Begin: /Users/michael/3dp/freeCAD/Grommet4David/load_grommet.FCMacro +++++++++++++++++++++++++++++++++++++++++++++++++

import FreeCAD as App
import os
import sys
from importlib import reload
os.chdir('/Users/michael/3dp/freeCAD/Grommet4David/')

if '' not in sys.path:
	sys.path.insert(0, '')

try:
	App.closeDocument('create_grommet')
except NameError:
	pass

App.newDocument('create_grommet')

if 'create_grommet' not in sys.modules:
    import create_grommet 
reload(create_grommet)

create_grommet.main()

#Gui.activeDocument().activeView().viewTop()
Gui.activeDocument().activeView().viewIsometric()
Gui.SendMsgToActiveView("ViewFit")

# Macro End: /Users/michael/3dp/freeCAD/Grommet4David/load_grommet.FCMacro +++++++++++++++++++++++++++++++++++++++++++++++++
