import os
import sys
import importlib
import FreeCAD
import Mesh

# Change to the directory containing the terrain generator
script_dir = os.path.dirname(os.path.realpath(__file__))
os.chdir(script_dir)

sys.path.append(script_dir)

# Remove terrain_generator from modules if it was previously imported
if 'terrain_generator' in sys.modules:
    del sys.modules['terrain_generator']


# Clear the report view
FreeCAD.Console.PrintMessage("\x1B[2J\x1B[H")

# Import the terrain generator module
import terrain_generator



for x,y in [(1,1), (1,2), (2,2), (3,3), (1,3)]:
	for n in range(20):
		n+=1  # count from 1
	# Close any open documents
		for doc in FreeCAD.listDocuments().values():
		    FreeCAD.closeDocument(doc.Name)
		
		# Create new terrain
		doc = terrain_generator.create_water_tile(x,y,wave_amplitude=0.8)
	
		# Set up the view
		Gui.activeDocument().activeView().viewIsometric()
		Gui.SendMsgToActiveView("ViewFit")
	
		# Redraw
		FreeCAD.ActiveDocument.recompute() 
	
	#	Gui.Selection.clearSelection()
	#	Gui.Selection.addSelection('Unnamed','WaterTerrain')
	#	Gui.runCommand('Std_Export',0)
		
		__objs__ = [FreeCAD.getDocument("Unnamed").getObject("WaterTerrain")]
	
		fn = f"/Users/michael/3dp/freeCAD/MaterMaze/Water/{x}x{y}v2-{n:02d}-WaterTerrian.stl"
		
		if hasattr(Mesh, "exportOptions"):
		    options = Mesh.exportOptions(fn)
		    Mesh.export(__objs__, fn, options)
		else:
		    Mesh.export(__objs__, fn)
